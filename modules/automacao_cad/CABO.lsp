;; CABO.lsp - Compativel com nanoCAD 5 gratuito (e AutoCAD)
;; Melhorias aplicadas: Gestao automatica de Layers e Modo Transformar.

(defun c:CABO (/ desc rede fase opc tipo cor ltype p1 p2 txtH pad pad_risco
                 char_w line_sp dcl_id dlg_result dcl_file f_dcl
                 v_rede v_fase v_opc_MT v_opc_BT v_desc_livre v_tipo
                 v_escala_fator escala_fator v_modo modo layer_name
                 sel ent entData entType pts i desenha_trecho mt_list mt_desc bt_list bt_desc)

  (vl-load-com)

  ;;; ============================================================
  ;;; CONFIGURACOES VISUAIS
  ;;; ============================================================
  (setq txtH      1.5
        pad       0.40
        pad_risco 0.15
        char_w    (* 1.5 0.72)
        line_sp   (* 1.5 1.6))

  ;;; ============================================================
  ;;; CRIAR DCL TEMPORARIO
  ;;; ============================================================
  (setq dcl_file (vl-filename-mktemp "CABO.dcl"))
  (setq f_dcl (open dcl_file "w"))
  (foreach line
    '(
      "cabo_dlg : dialog {"
      "  label = \"Cabo - Configuracao\";"
      "  width = 54;"
      "  : text { label = \"--- REDE E FASE ---\"; width = 50; }"
      "  : row {"
      "    : text { label = \"Rede:\"; width = 22; }"
      "    : radio_button { key = \"rede_MT\"; label = \"MT\"; }"
      "    : radio_button { key = \"rede_BT\"; label = \"BT\"; }"
      "  }"
      "  : row {"
      "    : text { label = \"Fase:\"; width = 22; }"
      "    : radio_button { key = \"fase_ABC\"; label = \"ABC\"; }"
      "    : radio_button { key = \"fase_AC\";  label = \"AC\"; }"
      "    : radio_button { key = \"fase_A\";   label = \"A\"; }"
      "    : radio_button { key = \"fase_B\";   label = \"B\"; }"
      "    : radio_button { key = \"fase_C\";   label = \"C\"; }"
      "  }"
      "  : spacer { height = 1; }"
      "  : text { label = \"--- ESCALA ---\"; width = 50; }"
      "  : row {"
      "    : text { label = \"Escala:\"; width = 22; }"
      "    : radio_button { key = \"escala_1000\"; label = \"1:1000\"; }"
      "    : radio_button { key = \"escala_500\";  label = \"1:500\"; }"
      "  }"
      "  : spacer { height = 1; }"
      "  : text { label = \"--- DESCRICAO DO CABO ---\"; width = 50; }"
      "  : row {"
      "    : text { label = \"Cabo (MT):\"; width = 22; }"
      "    : popup_list { key = \"opc_MT\"; width = 24; }"
      "  }"
      "  : row {"
      "    : text { label = \"Cabo (BT):\"; width = 22; }"
      "    : popup_list { key = \"opc_BT\"; width = 28; }"
      "  }"
      "  : row {"
      "    : text { label = \"Descricao livre:\"; width = 22; }"
      "    : edit_box { key = \"desc_livre\"; width = 24; }"
      "  }"
      "  : spacer { height = 1; }"
      "  : text { label = \"--- OPERACAO ---\"; width = 50; }"
      "  : row {"
      "    : text { label = \"Operacao:\"; width = 22; }"
      "    : radio_button { key = \"tipo_I\"; label = \"Instalando\"; }"
      "    : radio_button { key = \"tipo_R\"; label = \"Removendo\"; }"
      "  }"
      "  : spacer { height = 1; }"
      "  : text { label = \"--- MODO DE EXECUCAO ---\"; width = 50; }"
      "  : row {"
      "    : text { label = \"Modo:\"; width = 22; }"
      "    : radio_button { key = \"modo_D\"; label = \"Desenhar\"; }"
      "    : radio_button { key = \"modo_T\"; label = \"Transformar\"; }"
      "  }"
      "  : spacer { height = 1; }"
      "  : row {"
      "    : button { key = \"accept\"; label = \"OK\";        is_default = true; width = 12; }"
      "    : button { key = \"cancel\"; label = \"Cancelar\"; is_cancel  = true; width = 12; }"
      "  }"
      "}"
    )
    (write-line line f_dcl)
  )
  (close f_dcl)

  ;;; ============================================================
  ;;; LISTAS
  ;;; ============================================================
  (setq mt_list (list "CAA 2" "CAA 4" "CAA 1/0" "CAA 4/0" "CAA 336,4"
                      "P 50 / CAZ 9,5" "P 120 / CAZ 9,5" "P 185 / CAZ 9,5" "CAL 2" "CAL 1/0" "CAL 4/0" "CAL 336,4" "Outro"))
  (setq mt_desc (list "CAA 2" "CAA 4" "CAA 1/0" "CAA 4/0" "CAA 336,4"
                      "P 50\\pCAZ 9,5" "P 120\\pCAZ 9,5" "P 185\\pCAZ 9,5" "CAL 2" "CAL 1/0" "CAL 4/0" "CAL 336,4" nil))
  (setq bt_list (list "M2x1x35+35" "M3x1x35+35" "M3x1x35+35 NI" "M3x1x70+70" "M3x1x70+70 NI"
                      "M3x1x120+70" "M3x1x120+70 NI" "CA 4" "CA 1/0 / CA 4" "Outro"))
  (setq bt_desc (list "M2x1x35+35" "M3x1x35+35" "M3x1x35+35 NI" "M3x1x70+70" "M3x1x70+70 NI"
                      "M3x1x120+70" "M3x1x120+70 NI" "CA 4" "CA 1/0\\pCA 4" nil))

  ;;; ============================================================
  ;;; ABRIR DIALOGO
  ;;; ============================================================
  (setq dcl_id (load_dialog dcl_file))
  (if (< dcl_id 0) 
    (progn (alert "Erro ao carregar CABO.dcl temporário.") (vl-file-delete dcl_file) (exit)))
  
  (if (not (new_dialog "cabo_dlg" dcl_id))
    (progn (alert "Erro ao abrir cabo_dlg.") (unload_dialog dcl_id) (vl-file-delete dcl_file) (exit)))

  (start_list "opc_MT") (foreach v mt_list (add_list v)) (end_list)
  (start_list "opc_BT") (foreach v bt_list (add_list v)) (end_list)

  ;; Valores Iniciais
  (set_tile "rede_MT"  "1") (set_tile "rede_BT"  "0")
  (set_tile "fase_ABC" "1") (set_tile "fase_AC"  "0") (set_tile "fase_A" "0") (set_tile "fase_B" "0") (set_tile "fase_C" "0")
  (set_tile "escala_1000" "1") (set_tile "escala_500"  "0")
  (set_tile "tipo_I"   "1") (set_tile "tipo_R"   "0")
  (set_tile "modo_D"   "1") (set_tile "modo_T"   "0")
  (mode_tile "opc_MT"     0) (mode_tile "opc_BT"     1) (mode_tile "desc_livre" 1)

  ;; Callbacks
  (action_tile "rede_MT" "(set_tile \"rede_MT\" \"1\") (set_tile \"rede_BT\" \"0\") (mode_tile \"opc_MT\" 0) (mode_tile \"opc_BT\" 1) (mode_tile \"desc_livre\" 1)")
  (action_tile "rede_BT" "(set_tile \"rede_MT\" \"0\") (set_tile \"rede_BT\" \"1\") (mode_tile \"opc_BT\" 0) (mode_tile \"opc_MT\" 1) (mode_tile \"desc_livre\" 1)")
  (action_tile "fase_ABC" "(set_tile \"fase_ABC\" \"1\") (set_tile \"fase_AC\" \"0\") (set_tile \"fase_A\" \"0\") (set_tile \"fase_B\" \"0\") (set_tile \"fase_C\" \"0\")")
  (action_tile "fase_AC" "(set_tile \"fase_ABC\" \"0\") (set_tile \"fase_AC\" \"1\") (set_tile \"fase_A\" \"0\") (set_tile \"fase_B\" \"0\") (set_tile \"fase_C\" \"0\")")
  (action_tile "fase_A" "(set_tile \"fase_ABC\" \"0\") (set_tile \"fase_AC\" \"0\") (set_tile \"fase_A\" \"1\") (set_tile \"fase_B\" \"0\") (set_tile \"fase_C\" \"0\")")
  (action_tile "fase_B" "(set_tile \"fase_ABC\" \"0\") (set_tile \"fase_AC\" \"0\") (set_tile \"fase_A\" \"0\") (set_tile \"fase_B\" \"1\") (set_tile \"fase_C\" \"0\")")
  (action_tile "fase_C" "(set_tile \"fase_ABC\" \"0\") (set_tile \"fase_AC\" \"0\") (set_tile \"fase_A\" \"0\") (set_tile \"fase_B\" \"0\") (set_tile \"fase_C\" \"1\")")
  (action_tile "escala_1000" "(set_tile \"escala_1000\" \"1\") (set_tile \"escala_500\" \"0\")")
  (action_tile "escala_500" "(set_tile \"escala_1000\" \"0\") (set_tile \"escala_500\" \"1\")")
  (action_tile "tipo_I" "(set_tile \"tipo_I\" \"1\") (set_tile \"tipo_R\" \"0\")")
  (action_tile "tipo_R" "(set_tile \"tipo_I\" \"0\") (set_tile \"tipo_R\" \"1\")")
  (action_tile "modo_D" "(set_tile \"modo_D\" \"1\") (set_tile \"modo_T\" \"0\")")
  (action_tile "modo_T" "(set_tile \"modo_D\" \"0\") (set_tile \"modo_T\" \"1\")")
  (action_tile "opc_MT" "(setq v_opc_MT (atoi $value)) (if (= v_opc_MT 12) (mode_tile \"desc_livre\" 0) (mode_tile \"desc_livre\" 1))")
  (action_tile "opc_BT" "(setq v_opc_BT (atoi $value)) (if (= v_opc_BT 9) (mode_tile \"desc_livre\" 0) (mode_tile \"desc_livre\" 1))")
  
  (action_tile "accept"
    "(setq v_rede       (if (= (get_tile \"rede_MT\") \"1\") \"MT\" \"BT\")
           v_fase       (cond ((= (get_tile \"fase_ABC\") \"1\") \"ABC\")
                              ((= (get_tile \"fase_AC\")  \"1\") \"AC\")
                              ((= (get_tile \"fase_A\")   \"1\") \"A\")
                              ((= (get_tile \"fase_B\")   \"1\") \"B\")
                              (T \"C\"))
           v_opc_MT     (atoi (get_tile \"opc_MT\"))
           v_opc_BT     (atoi (get_tile \"opc_BT\"))
           v_desc_livre (get_tile \"desc_livre\")
           v_tipo       (if (= (get_tile \"tipo_I\") \"1\") \"I\" \"R\")
           v_escala_fator (if (= (get_tile \"escala_500\") \"1\") 2.0 1.0)
           v_modo       (if (= (get_tile \"modo_D\") \"1\") \"D\" \"T\"))
     (done_dialog 1)")

  (setq dlg_result (start_dialog))
  (unload_dialog dcl_id)
  (vl-file-delete dcl_file)

  (if (/= dlg_result 1) (progn (princ "\nCancelado.") (princ) (exit)))

  ;;; ============================================================
  ;;; POS-DIALOGO (Carrega Variáveis)
  ;;; ============================================================
  (setq rede         v_rede
        fase         v_fase
        tipo         v_tipo
        escala_fator v_escala_fator
        modo         v_modo)
        
  (if (= rede "MT")
    (setq desc (if (= v_opc_MT 12) v_desc_livre (nth v_opc_MT mt_desc)))
    (setq desc (if (= v_opc_BT 9) v_desc_livre (nth v_opc_BT bt_desc))))
  (if (not desc) (setq desc ""))

  (setq cor   (if (= tipo "I") 1 8)
        ltype "Continuous")
  (if (= rede "MT")
    (cond ((tblsearch "ltype" "TRACEJADA") (setq ltype "TRACEJADA"))
          ((tblsearch "ltype" "DASHED")    (setq ltype "DASHED"))
          ((tblsearch "ltype" "HIDDEN")    (setq ltype "HIDDEN"))))

  ;;; ============================================================
  ;;; GERENCIAMENTO DE CAMADAS (LAYERS)
  ;;; ============================================================
  (setq layer_name (strcat "REDE_" rede))
  (if (not (tblsearch "LAYER" layer_name))
    (entmake (list '(0 . "LAYER")
                   '(100 . "AcDbSymbolTableRecord")
                   '(100 . "AcDbLayerTableRecord")
                   (cons 2 layer_name)
                   '(70 . 0)
                   (cons 62 (if (= rede "MT") 1 2))))) ; Cores padrao para nova layer: 1(red) MT / 2(yellow) BT

  ;;; ============================================================
  ;;; FUNCAO AUXILIAR: DESENHAR TRECHO (Processa 1 Segmento)
  ;;; ============================================================
  (defun desenha_trecho (pt1 pt2 / dist distTxt txt ang_orig ang midPt off txtPt max_len cur_len idx lines_len num_linhas total_h total_w dx_left dx_right p_A p_B p_C p_D top_offset i_idx w_i y_offset_i C_i pR1 pR2 char)
    (setq dist    (fix (+ (/ (distance pt1 pt2) escala_fator) 0.5))
          distTxt (itoa dist)
          txt     (strcat " " desc " " fase " " distTxt " m "))
          
    (while (vl-string-search "\\p" txt)
      (setq txt (vl-string-subst " \\P " "\\p" txt)))
      
    (setq ang_orig (angle pt1 pt2)
          ang      ang_orig)
          
    (entmake (list '(0 . "LINE") (cons 8 layer_name) (cons 10 pt1) (cons 11 pt2) (cons 62 cor) (cons 6 ltype)))
    
    (if (and (> ang_orig (/ pi 2)) (<= ang_orig (* pi 1.5)))
      (setq ang (- ang pi)))
      
    (setq max_len 0 cur_len 0 idx 1 lines_len '())
    (while (<= idx (strlen txt))
      (setq char (substr txt idx 2))
      (if (= char "\\P")
        (progn
          (setq lines_len (append lines_len (list cur_len)))
          (if (> cur_len max_len) (setq max_len cur_len))
          (setq cur_len 0 idx (+ idx 2)))
        (progn (setq cur_len (1+ cur_len) idx (1+ idx)))))
    (setq lines_len (append lines_len (list cur_len)))
    (if (> cur_len max_len) (setq max_len cur_len))
    
    (setq num_linhas (length lines_len)
          total_h    (+ txtH (* (1- num_linhas) line_sp))
          total_w    (* max_len char_w))
          
    (setq midPt (mapcar '(lambda (a b) (/ (+ a b) 2.0)) pt1 pt2)
          off   (+ 1.0 (/ total_h 2.0)))
    (if (and (> ang_orig (/ pi 2)) (<= ang_orig (* pi 1.5)))
      (setq txtPt (polar midPt (- ang (/ pi 2)) off))
      (setq txtPt (polar midPt (+ ang (/ pi 2)) off)))
      
    (entmake (list '(0 . "MTEXT") '(100 . "AcDbEntity") '(100 . "AcDbMText") (cons 8 layer_name)
                   (cons 10 txtPt) (cons 40 txtH) (cons 41 0.0) (cons 71 5)
                   (cons 1 txt) (cons 50 ang) (cons 62 cor)))
                   
    (if (= tipo "I")
      (progn
        (setq dx_left  (polar txtPt (+ ang pi) (+ (/ total_w 2.0) pad))
              dx_right (polar txtPt ang          (+ (/ total_w 2.0) pad))
              p_A      (polar dx_left  (- ang (/ pi 2)) (+ (/ total_h 2.0) pad))
              p_B      (polar dx_right (- ang (/ pi 2)) (+ (/ total_h 2.0) pad))
              p_C      (polar dx_right (+ ang (/ pi 2)) (+ (/ total_h 2.0) pad))
              p_D      (polar dx_left  (+ ang (/ pi 2)) (+ (/ total_h 2.0) pad)))
        (entmake (list '(0 . "LWPOLYLINE") '(100 . "AcDbEntity") '(100 . "AcDbPolyline") (cons 8 layer_name)
                       '(90 . 4) '(70 . 1) (cons 62 cor)
                       (cons 10 p_A) (cons 10 p_B) (cons 10 p_C) (cons 10 p_D)))))
                       
    (if (= tipo "R")
      (progn
        (setq i_idx 0 top_offset (/ (* (1- num_linhas) line_sp) 2.0))
        (while (< i_idx num_linhas)
          (setq w_i        (* (nth i_idx lines_len) char_w)
                y_offset_i (- top_offset (* i_idx line_sp))
                C_i        (polar txtPt (+ ang (/ pi 2)) y_offset_i)
                pR1        (polar C_i (+ ang pi) (+ (/ w_i 2.0) pad_risco))
                pR2        (polar C_i ang          (+ (/ w_i 2.0) pad_risco)))
          (entmake (list '(0 . "LINE") (cons 8 layer_name) (cons 10 pR1) (cons 11 pR2) (cons 62 cor)))
          (setq i_idx (1+ i_idx)))))
  )

  ;;; ============================================================
  ;;; ROTINAS DE INSERCAO (MODO DESENHAR OU TRANSFORMAR)
  ;;; ============================================================
  (if (= modo "D")
    (progn
      (setq p1 (getpoint "\nClique no ponto inicial: "))
      (while (setq p2 (getpoint p1 "\nProximo ponto ou digite a distancia final no desenho (ENTER para sair): "))
        (desenha_trecho p1 p2)
        (setq p1 p2)
      )
    )
    (progn
      (while (setq sel (entsel "\nSelecione a linha ou polilinha para transformar (ENTER para sair): "))
        (setq ent (car sel)
              entData (entget ent)
              entType (cdr (assoc 0 entData)))
        (cond
          ((= entType "LINE")
           (setq p1 (cdr (assoc 10 entData))
                 p2 (cdr (assoc 11 entData)))
           (desenha_trecho p1 p2)
           (entdel ent) ; Remove a entidade original apos transformacao
          )
          ((= entType "LWPOLYLINE")
           ;; Filtra e extrai todos os codigos de grupo 10 convertendo para coordenadas X,Y,Z
           (setq pts (mapcar '(lambda (x) (list (cadr x) (caddr x) 0.0)) (vl-remove-if-not '(lambda (x) (= (car x) 10)) entData)))
           (setq i 0)
           (while (< i (1- (length pts)))
             (setq p1 (nth i pts)
                   p2 (nth (1+ i) pts))
             (desenha_trecho p1 p2)
             (setq i (1+ i))
           )
           (entdel ent) ; Remove a entidade original apos transformacao
          )
          (T (princ "\nEntidade invalida. Selecione uma LINE ou LWPOLYLINE."))
        )
      )
    )
  )
  
  (princ "\nComando CABO concluido.")
  (princ)
)
